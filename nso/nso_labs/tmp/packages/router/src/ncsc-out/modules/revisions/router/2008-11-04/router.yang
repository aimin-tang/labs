module router {
  // Generated by yanger -t ncs
  tailf:ncs-device-type "netconf";

  namespace "http://example.com/router";
  prefix r;

  include router-types;
  include router-interfaces;
  include router-syslog;
  include router-dns;
  include router-ntp;
  include router-routes;
  import tailf-ncs {
    prefix ncs;
  }
  import tailf-common {
    prefix tailf;
  }

  organization "tail-f";
  description
    "An example module describing some common components typically found
     on routers

      interfaces - configuration and status of network interfaces
      routes     - configuration of static routes
      syslog     - configuration of logging to remote syslog servers
      dns        - configuration of the DNS resolver
      ntp        - configuration and status of the NTP daemon

     This module is the main YANG module, and each component has its
     own YANG submodule.";

  revision 2008-11-04 {
    description
      "draft-ietf-netmod-yang-02 compatible.";
  }
  revision 2007-08-29 {
    description
      "Syntax fixes after pyang validation.";
  }
  revision 2007-06-08 {
    description
      "Initial revision.";
  }

  augment "/ncs:devices/ncs:device/ncs:config" {
    container sys {
      tailf:ncs-device-type "netconf";
      tailf:display-when "not(../../ncs:module) or ../../ncs:module[ncs:name='router']";
      container interfaces {
        uses interfaces;
      }
      container routes {
        uses routes;
      }
      container syslog {
        uses syslog;
      }
      container ntp {
        uses ntp;
      }
      container dns {
        uses dns;
      }
    }
  }
  augment "/ncs:devices/ncs:device/ncs:live-status" {
    container sys {
      tailf:ncs-device-type "netconf";
      tailf:display-when "not(../../ncs:module) or ../../ncs:module[ncs:name='router'] or (../../ncs:live-status-protocol[not(ncs:capability)]) or (../../ncs:live-status-protocol/ncs:capability/ncs:module[.='router'])";
      container interfaces {
        uses live_ncs_interfaces;
      }
      container routes {
        uses live_ncs_routes;
      }
      container syslog {
        uses live_ncs_syslog;
      }
      container ntp {
        uses live_ncs_ntp;
      }
      container dns {
        uses live_ncs_dns;
      }
    }
  }
  augment "/ncs:devices/ncs:template/ncs:config" {
    container sys {
      container interfaces {
        uses ncs_template_interfaces;
      }
      container routes {
        uses ncs_template_routes;
      }
      container syslog {
        uses ncs_template_syslog;
      }
      container ntp {
        uses ncs_template_ntp;
      }
      container dns {
        uses ncs_template_dns;
      }
    }
  }
}
