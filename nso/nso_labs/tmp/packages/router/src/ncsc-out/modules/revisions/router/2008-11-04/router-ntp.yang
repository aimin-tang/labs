submodule router-ntp {
  // Generated by yanger -t ncs
  belongs-to router {
    prefix r;
  }

  import ietf-inet-types {
    prefix inet;
  }
  include router-types;
  import tailf-ncs {
    prefix ncs;
  }
  import tailf-common {
    prefix tailf;
  }

  description
    "The 'ntp' component provides support for configuring
     the ntpd daemon from the reference NTP implementation. It
     also provides status information pertaining to the configured
     servers.

     The set of configurable parameters has been limited to
     those that may be generally useful on a network device,
     including

         - remote servers/peers
         - local-clock server
         - access control
         - symmetric-key based authentication";

  revision 2008-11-04 {
    description
      "draft-ietf-netmod-yang-02 compatible.";
  }
  revision 2007-08-29 {
    description
      "Syntax fixes after pyang validation.";
  }
  revision 2007-06-08 {
    description
      "Initial revision.";
  }

  typedef ntpKeyValue {
    type string {
      pattern '[!-~]{1,32}';
    }
  }

  typedef ntpRestrictFlag {
    type enumeration {
      enum "ignore";
      enum "kod";
      enum "limited";
      enum "lowpriotrap";
      enum "nomodify";
      enum "nopeer";
      enum "noquery";
      enum "noserve";
      enum "notrap";
      enum "notrust";
      enum "ntpport";
      enum "version";
    }
  }

  typedef ntpRestrictMask {
    type union {
      type enumeration {
        enum "default";
      }
      type inet:ip-address;
    }
  }

  typedef ntpRestrictName {
    type union {
      type enumeration {
        enum "default";
      }
      type inet:host;
    }
  }

  typedef ntpDecimal {
    type int32;
    units "milliseconds";
  }

  typedef ntpStratum {
    type uint8 {
      range "0..15";
    }
  }

  typedef ntpState {
    type enumeration {
      enum "reject";
      enum "falsetick";
      enum "excess";
      enum "outlyer";
      enum "candidate";
      enum "selected";
      enum "syspeer";
      enum "ppspeer";
      enum "unknown";
    }
  }

  grouping ncs_template_ntpStatus {
    leaf state {
      type string;
    }
    leaf stratum {
      type string;
    }
    leaf reach {
      type string;
    }
    leaf delay {
      type string;
    }
    leaf offset {
      type string;
    }
    leaf jitter {
      type string;
    }
  }

  grouping ncs_template_ntp {
    list server {
      // NCS patched for predictable order
      ordered-by user;
      key "name";
      // NCS drop max-elements statement
      leaf name {
        type string;
      }
      leaf enabled {
        type string;
        // NCS drop default statement
      }
      leaf peer {
        type string;
        // NCS drop default statement
      }
      leaf iburst {
        type empty;
      }
      leaf version {
        type string;
        // NCS drop default statement
      }
      leaf key {
        type string;
      }
      // NCS drop config false container status
    }
    container local-clock {
      leaf enabled {
        type string;
        // NCS drop default statement
      }
      leaf stratum {
        type string;
        // NCS drop default statement
      }
      container status {
        uses ncs_template_ntpStatus;
      }
    }
    list restrict {
      // NCS patched for predictable order
      ordered-by user;
      key "name mask";
      // NCS drop max-elements statement
      leaf name {
        type string;
      }
      leaf mask {
        type string;
      }
      leaf-list flag {
        // NCS patched for predictable order
        ordered-by user;
        type string;
      }
    }
    list key {
      // NCS patched for predictable order
      ordered-by user;
      key "name";
      // NCS drop max-elements statement
      leaf name {
        type string;
      }
      leaf value {
        type string;
      }
      leaf trusted {
        type string;
        // NCS drop default statement
      }
    }
    leaf requestkey {
      type string;
    }
    leaf controlkey {
      type string;
    }
  }

  grouping ncs_rpc_notif_ntpStatus {
    leaf state {
      type ntpState;
    }
    leaf stratum {
      type ntpStratum;
    }
    leaf reach {
      type string;
    }
    leaf delay {
      type ntpDecimal;
    }
    leaf offset {
      type ntpDecimal;
    }
    leaf jitter {
      type ntpDecimal;
    }
  }

  grouping ncs_rpc_notif_ntp {
    list server {
      key "name";
      max-elements 16;
      leaf name {
        type inet:host;
      }
      leaf enabled {
        type boolean;
        default "true";
      }
      leaf peer {
        type boolean;
        default "false";
      }
      leaf iburst {
        type empty;
      }
      leaf version {
        type int8 {
          range "1..4";
        }
        default "4";
      }
      leaf key {
        type leafref {
          path "../../key/name";
        }
      }
      container status {
        config false;
        uses ncs_rpc_notif_ntpStatus;
      }
    }
    container local-clock {
      leaf enabled {
        type boolean;
        default "true";
      }
      leaf stratum {
        type ntpStratum;
        default "10";
      }
      container status {
        uses ncs_rpc_notif_ntpStatus;
      }
    }
    list restrict {
      key "name mask";
      max-elements 64;
      leaf name {
        type ntpRestrictName;
      }
      leaf mask {
        type ntpRestrictMask;
      }
      leaf-list flag {
        type ntpRestrictFlag;
      }
    }
    list key {
      key "name";
      max-elements 64;
      leaf name {
        type uint8 {
          range "1..max";
        }
      }
      leaf value {
        type ntpKeyValue;
      }
      leaf trusted {
        type boolean;
        default "true";
      }
    }
    leaf requestkey {
      type leafref {
        path "../key/name";
      }
    }
    leaf controlkey {
      type leafref {
        path "../key/name";
      }
    }
  }

  grouping live_ncs_ntpStatus {
    leaf state {
      type ntpState;
    }
    leaf stratum {
      type ntpStratum;
    }
    leaf reach {
      type string;
    }
    leaf delay {
      type ntpDecimal;
    }
    leaf offset {
      type ntpDecimal;
    }
    leaf jitter {
      type ntpDecimal;
    }
  }

  grouping live_ncs_ntp {
    list server {
      key "name";
      // NCS drop max-elements statement
      leaf name {
        type inet:host;
      }
      leaf enabled {
        type boolean;
        // NCS drop default statement
      }
      leaf peer {
        type boolean;
        // NCS drop default statement
      }
      leaf iburst {
        type empty;
      }
      leaf version {
        type int8 {
          range "1..4";
        }
        // NCS drop default statement
      }
      leaf key {
        type leafref {
          path "../../key/name";
        }
      }
      container status {
        uses live_ncs_ntpStatus;
      }
    }
    container local-clock {
      leaf enabled {
        type boolean;
        // NCS drop default statement
      }
      leaf stratum {
        type ntpStratum;
        // NCS drop default statement
      }
      container status {
        uses live_ncs_ntpStatus;
      }
    }
    list restrict {
      key "name mask";
      // NCS drop max-elements statement
      leaf name {
        type ntpRestrictName;
      }
      leaf mask {
        type ntpRestrictMask;
      }
      leaf-list flag {
        type ntpRestrictFlag;
      }
    }
    list key {
      key "name";
      // NCS drop max-elements statement
      leaf name {
        type uint8 {
          range "1..max";
        }
      }
      leaf value {
        type ntpKeyValue;
      }
      leaf trusted {
        type boolean;
        // NCS drop default statement
      }
    }
    leaf requestkey {
      type leafref {
        path "../key/name";
      }
    }
    leaf controlkey {
      type leafref {
        path "../key/name";
      }
    }
  }

  grouping ntpStatus {
    leaf state {
      type ntpState;
    }
    leaf stratum {
      type ntpStratum;
    }
    leaf reach {
      type string;
    }
    leaf delay {
      type ntpDecimal;
    }
    leaf offset {
      type ntpDecimal;
    }
    leaf jitter {
      type ntpDecimal;
    }
  }

  grouping ntp {
    list server {
      key "name";
      max-elements 16;
      leaf name {
        type inet:host;
      }
      leaf enabled {
        type boolean;
        default "true";
      }
      leaf peer {
        type boolean;
        default "false";
      }
      leaf iburst {
        type empty;
      }
      leaf version {
        type int8 {
          range "1..4";
        }
        default "4";
      }
      leaf key {
        type leafref {
          path "../../key/name";
        }
      }
      // NCS drop config false container status
    }
    container local-clock {
      leaf enabled {
        type boolean;
        default "true";
      }
      leaf stratum {
        type ntpStratum;
        default "10";
      }
      container status {
        uses ntpStatus;
      }
    }
    list restrict {
      key "name mask";
      max-elements 64;
      leaf name {
        type ntpRestrictName;
      }
      leaf mask {
        type ntpRestrictMask;
      }
      leaf-list flag {
        type ntpRestrictFlag;
      }
    }
    list key {
      key "name";
      max-elements 64;
      leaf name {
        type uint8 {
          range "1..max";
        }
      }
      leaf value {
        type ntpKeyValue;
      }
      leaf trusted {
        type boolean;
        default "true";
      }
    }
    leaf requestkey {
      type leafref {
        path "../key/name";
      }
    }
    leaf controlkey {
      type leafref {
        path "../key/name";
      }
    }
  }
}
