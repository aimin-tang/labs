submodule router-dns {
  // Generated by yanger -t ncs
  belongs-to router {
    prefix r;
  }

  import ietf-inet-types {
    prefix inet;
  }
  include router-types;
  import tailf-ncs {
    prefix ncs;
  }
  import tailf-common {
    prefix tailf;
  }

  description
    "The 'dns' component provides support for configuring the DNS resolver.

     The 'domain' keyword of /etc/resolv.conf is not supported, since
     it is equivalent to 'search' with a single domain. I.e. in terms
     of the data model, the domains are always configured as 'search'
     elements, even if there is only one. The set of available options
     has been limited to those that are generally available across
     different resolver implementations, and generally useful.";

  revision 2008-11-04 {
    description
      "draft-ietf-netmod-yang-02 compatible.";
  }
  revision 2007-08-29 {
    description
      "Syntax fixes after pyang validation.";
  }
  revision 2007-06-08 {
    description
      "Initial revision.";
  }

  grouping ncs_template_dns {
    list search {
      // NCS patched for predictable order
      ordered-by user;
      key "name";
      // NCS drop max-elements statement
      leaf name {
        type string;
      }
      leaf domain {
        type string;
      }
    }
    list server {
      // NCS patched for predictable order
      ordered-by user;
      key "address";
      // NCS drop max-elements statement
      leaf address {
        type string;
      }
    }
    container options {
      leaf ndots {
        type string;
      }
      leaf timeout {
        type string;
      }
      leaf attempts {
        type string;
      }
    }
  }

  grouping ncs_rpc_notif_dns {
    list search {
      key "name";
      max-elements 3;
      leaf name {
        type int32;
      }
      leaf domain {
        type inet:host;
      }
    }
    list server {
      key "address";
      max-elements 3;
      ordered-by user;
      leaf address {
        type inet:ip-address;
      }
    }
    container options {
      leaf ndots {
        type uint8;
      }
      leaf timeout {
        type uint8;
      }
      leaf attempts {
        type uint8;
      }
    }
  }

  grouping live_ncs_dns {
    list search {
      key "name";
      // NCS drop max-elements statement
      leaf name {
        type int32;
      }
      leaf domain {
        type inet:host;
      }
    }
    list server {
      key "address";
      // NCS drop max-elements statement
      ordered-by user;
      leaf address {
        type inet:ip-address;
      }
    }
    container options {
      leaf ndots {
        type uint8;
      }
      leaf timeout {
        type uint8;
      }
      leaf attempts {
        type uint8;
      }
    }
  }

  grouping dns {
    list search {
      key "name";
      max-elements 3;
      leaf name {
        type int32;
      }
      leaf domain {
        type inet:host;
      }
    }
    list server {
      key "address";
      max-elements 3;
      ordered-by user;
      leaf address {
        type inet:ip-address;
      }
    }
    container options {
      leaf ndots {
        type uint8;
      }
      leaf timeout {
        type uint8;
      }
      leaf attempts {
        type uint8;
      }
    }
  }
}
