module tailf-ned-cisco-asa-stats {
  // Generated by yanger -t ncs
  tailf:ncs-device-type "cli-ned";

  namespace "http://cisco.com/ned/asa-stats";
  prefix asa-stats;

  import tailf-common {
    prefix tailf;
  }
  import tailf-ncs {
    prefix ncs;
  }

  augment "/ncs:devices/ncs:device/ncs:live-status" {
    container vpn-sessiondb {
      tailf:ncs-device-type "cli-ned";
      tailf:display-when "not(../../ncs:module) or ../../ncs:module[ncs:name='tailf-ned-cisco-asa-stats'] or (../../ncs:live-status-protocol[not(ncs:capability)]) or (../../ncs:live-status-protocol/ncs:capability/ncs:module[.='tailf-ned-cisco-asa-stats'])";
      list anyconnect {
        key "username index";
        leaf username {
          type string;
        }
        leaf index {
          type uint32;
        }
        leaf login-time {
          type string;
        }
        leaf duration {
          type string;
        }
        leaf inactivity {
          type string;
        }
        leaf tx-bytes {
          type uint64;
        }
        leaf rx-bytes {
          type uint64;
        }
        leaf status {
          type enumeration {
            enum "active";
            enum "inactive";
          }
        }
      }
    }
    container inside-interface {
      tailf:ncs-device-type "cli-ned";
      tailf:display-when "not(../../ncs:module) or ../../ncs:module[ncs:name='tailf-ned-cisco-asa-stats'] or (../../ncs:live-status-protocol[not(ncs:capability)]) or (../../ncs:live-status-protocol/ncs:capability/ncs:module[.='tailf-ned-cisco-asa-stats'])";
      leaf line-protocol-status {
        type enumeration {
          enum "up";
          enum "down";
        }
        // NCS drop default statement
      }
      leaf input-bytes {
        type uint64;
      }
      leaf output-bytes {
        type uint64;
      }
      leaf input-rate {
        type uint32;
      }
      leaf output-rate {
        type uint32;
      }
    }
    container ssl {
      tailf:ncs-device-type "cli-ned";
      tailf:display-when "not(../../ncs:module) or ../../ncs:module[ncs:name='tailf-ned-cisco-asa-stats'] or (../../ncs:live-status-protocol[not(ncs:capability)]) or (../../ncs:live-status-protocol/ncs:capability/ncs:module[.='tailf-ned-cisco-asa-stats'])";
      leaf post-decrypt-octets {
        type uint64;
      }
      leaf post-encrypt-octets {
        type uint64;
      }
    }
    container exec {
      tailf:ncs-device-type "cli-ned";
      tailf:display-when "not(../../ncs:module) or ../../ncs:module[ncs:name='tailf-ned-cisco-asa-stats'] or (../../ncs:live-status-protocol[not(ncs:capability)]) or (../../ncs:live-status-protocol/ncs:capability/ncs:module[.='tailf-ned-cisco-asa-stats'])";
      tailf:info
        "Execute commands on device";
      tailf:action show {
        tailf:actionpoint ncsproxy {
          tailf:internal;
        }
        tailf:info
          "Execute show commands";
        // NCS drop tailf:actionpoint
        input {
          leaf-list args {
            tailf:cli-drop-node-name;
            tailf:cli-flat-list-syntax;
            type string {
              tailf:info
                "show argument(s)";
            }
          }
        }
        output {
          leaf result {
            type string;
          }
        }
      }
      tailf:action clear {
        tailf:actionpoint ncsproxy {
          tailf:internal;
        }
        tailf:info
          "Reset functions";
        // NCS drop tailf:actionpoint
        input {
          leaf-list args {
            tailf:cli-drop-node-name;
            tailf:cli-flat-list-syntax;
            type string {
              tailf:info
                "clear argument(s)";
            }
          }
        }
        output {
          leaf result {
            type string;
          }
        }
      }
      tailf:action license {
        tailf:actionpoint ncsproxy {
          tailf:internal;
        }
        tailf:info
          "Register/deregister the product instance with the Cisco Licensing Authority";
        // NCS drop tailf:actionpoint
        input {
          leaf-list args {
            tailf:cli-drop-node-name;
            tailf:cli-flat-list-syntax;
            type string {
              tailf:info
                "USAGE:;;license smart deregister|register|renew [options]";
            }
          }
        }
        output {
          leaf result {
            type string;
          }
        }
      }
      tailf:action any {
        tailf:actionpoint ncsproxy {
          tailf:internal;
        }
        tailf:info
          "Execute any command on device";
        // NCS drop tailf:actionpoint
        input {
          leaf context {
            tailf:info
              "Specify context to run the command in";
            type string {
              tailf:info
                "WORD;;Context name";
            }
          }
          leaf-list args {
            tailf:cli-drop-node-name;
            tailf:cli-flat-list-syntax;
            type string {
              tailf:info
                "WORD;;any [context <context>] \"<cmd> [option(s)]\", e.g: any \"show ppp summary\"";
            }
          }
        }
        output {
          leaf result {
            type string;
          }
        }
      }
    }
  }
}
