module tailf-ned-cisco-asa-id {
  // Generated by yanger -t ncs
  tailf:ncs-device-type "cli-ned";

  namespace "http://cisco.com/ned/asa-id";
  prefix asa-id;

  import tailf-ncs-ned {
    prefix ned;
  }
  import tailf-ncs {
    prefix ncs;
  }
  import tailf-common {
    prefix tailf;
  }

  identity cisco-asa {
    base ned:cli-ned-id;
  }
}
